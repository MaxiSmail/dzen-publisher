(vl-load-com)
(defun c:CREATE_POPOVKA_SCHEMES_V2 ( / old_echo old_osm)
  (setq old_echo (getvar "CMDECHO"))
  (setq old_osm (getvar "OSMODE"))
  (setvar "CMDECHO" 0)
  (setvar "OSMODE" 0)
  ;; Включаем отображение весов линий
  (setvar "LWDISPLAY" 1)
  (princ "\n--- ГЕНЕРАЦИЯ ОБНОВЛЕННЫХ ИСПОЛНИТЕЛЬНЫХ СХЕМ (V2) ---\n")
  ;; Настройка текстового стиля ISOCPEUR
  (if (null (tblobjname "STYLE" "ISOCPEUR"))
    (command "_.style" "ISOCPEUR" "isocpeur.ttf,arial.ttf" "0" "1" "0" "_N" "_N")
    (setvar "TEXTSTYLE" "ISOCPEUR")
  )
  (if (null (tblobjname "LAYER" "ИС_Рамка_Толстая"))
    (command "_.layer" "_m" "ИС_Рамка_Толстая" "_c" 7 "ИС_Рамка_Толстая" "_lw" 70 "ИС_Рамка_Толстая" "")
  )
  (if (null (tblobjname "LAYER" "ИС_Штамп_Контур"))
    (command "_.layer" "_m" "ИС_Штамп_Контур" "_c" 7 "ИС_Штамп_Контур" "_lw" 50 "ИС_Штамп_Контур" "")
  )
  (if (null (tblobjname "LAYER" "ИС_Штамп_Тонкая"))
    (command "_.layer" "_m" "ИС_Штамп_Тонкая" "_c" 7 "ИС_Штамп_Тонкая" "_lw" 20 "ИС_Штамп_Тонкая" "")
  )
  (if (null (tblobjname "LAYER" "ИС_Контур_Толстый"))
    (command "_.layer" "_m" "ИС_Контур_Толстый" "_c" 4 "ИС_Контур_Толстый" "_lw" 60 "ИС_Контур_Толстый" "")
  )
  (if (null (tblobjname "LAYER" "ИС_Демонтаж_Кладка"))
    (command "_.layer" "_m" "ИС_Демонтаж_Кладка" "_c" 1 "ИС_Демонтаж_Кладка" "_lw" 60 "ИС_Демонтаж_Кладка" "")
  )
  (if (null (tblobjname "LAYER" "ИС_Демонтаж_Профлист"))
    (command "_.layer" "_m" "ИС_Демонтаж_Профлист" "_c" 140 "ИС_Демонтаж_Профлист" "_lw" 40 "ИС_Демонтаж_Профлист" "")
  )
  (if (null (tblobjname "LAYER" "ИС_Демонтаж_Металл"))
    (command "_.layer" "_m" "ИС_Демонтаж_Металл" "_c" 8 "ИС_Демонтаж_Металл" "_lw" 50 "ИС_Демонтаж_Металл" "")
  )
  (if (null (tblobjname "LAYER" "ИС_Арматура_Рабочая"))
    (command "_.layer" "_m" "ИС_Арматура_Рабочая" "_c" 2 "ИС_Арматура_Рабочая" "_lw" 70 "ИС_Арматура_Рабочая" "")
  )
  (if (null (tblobjname "LAYER" "ИС_Арматура_Хомуты"))
    (command "_.layer" "_m" "ИС_Арматура_Хомуты" "_c" 6 "ИС_Арматура_Хомуты" "_lw" 35 "ИС_Арматура_Хомуты" "")
  )
  (if (null (tblobjname "LAYER" "ИС_Бетон_Контур"))
    (command "_.layer" "_m" "ИС_Бетон_Контур" "_c" 5 "ИС_Бетон_Контур" "_lw" 60 "ИС_Бетон_Контур" "")
  )
  (if (null (tblobjname "LAYER" "ИС_Тонкая"))
    (command "_.layer" "_m" "ИС_Тонкая" "_c" 8 "ИС_Тонкая" "_lw" 18 "ИС_Тонкая" "")
  )
  (if (null (tblobjname "LAYER" "ИС_Оси"))
    (command "_.layer" "_m" "ИС_Оси" "_c" 1 "ИС_Оси" "_lw" 18 "ИС_Оси" "")
  )
  (if (null (tblobjname "LAYER" "ИС_Размеры"))
    (command "_.layer" "_m" "ИС_Размеры" "_c" 3 "ИС_Размеры" "_lw" 18 "ИС_Размеры" "")
  )
  (if (null (tblobjname "LAYER" "ИС_Текст_Основной"))
    (command "_.layer" "_m" "ИС_Текст_Основной" "_c" 7 "ИС_Текст_Основной" "_lw" 25 "ИС_Текст_Основной" "")
  )
  (if (null (tblobjname "LAYER" "ИС_Таблицы_Сетка"))
    (command "_.layer" "_m" "ИС_Таблицы_Сетка" "_c" 7 "ИС_Таблицы_Сетка" "_lw" 35 "ИС_Таблицы_Сетка" "")
  )
  (if (null (tblobjname "LAYER" "ИС_Таблицы_Тонкая"))
    (command "_.layer" "_m" "ИС_Таблицы_Тонкая" "_c" 8 "ИС_Таблицы_Тонкая" "_lw" 18 "ИС_Таблицы_Тонкая" "")
  )

  (defun _l (p1 p2 lay)
    (entmake (list '(0 . "LINE") (cons 8 lay) (cons 10 p1) (cons 11 p2)))
  )
  (defun _r (p1 p2 lay)
    (let ((x1 (car p1)) (y1 (cadr p1))
          (x2 (car p2)) (y2 (cadr p2)))
      (entmake (list '(0 . "LWPOLYLINE") '(100 . "AcDbEntity") (cons 8 lay)
                     '(100 . "AcDbPolyline") '(90 . 4) '(70 . 1)
                     (cons 10 (list x1 y1))
                     (cons 10 (list x2 y1))
                     (cons 10 (list x2 y2))
                     (cons 10 (list x1 y2))
               ))
    )
  )
  (defun _c (cen rad lay)
    (entmake (list '(0 . "CIRCLE") (cons 8 lay) (cons 10 cen) (cons 40 rad)))
  )
  (defun _t (str pt h lay align)
    (let ((flag (cond ((= align "C") 1) ((= align "R") 2) (t 0))))
      (if (= flag 0)
        (entmake (list '(0 . "TEXT") (cons 8 lay) (cons 7 "ISOCPEUR") (cons 10 pt) (cons 40 h) (cons 1 str)))
        (entmake (list '(0 . "TEXT") (cons 8 lay) (cons 7 "ISOCPEUR") (cons 10 pt) (cons 11 pt) (cons 40 h)
                       (cons 1 str) (cons 72 flag) (cons 73 0)))
      )
    )
  )
  (defun _frame (bx by s-num s-title)
    (_r (list bx by 0.0) (list (+ bx 21000.0) (+ by 14850.0) 0.0) "ИС_Рамка_Толстая")
    (setq ix1 (+ bx 1000.0) iy1 (+ by 250.0)
          ix2 (+ bx 20750.0) iy2 (+ by 14600.0))
    (_r (list ix1 iy1 0.0) (list ix2 iy2 0.0) "ИС_Рамка_Толстая")
    
    (setq sx1 (- ix2 9250.0) sy1 iy1
          sx2 ix2 sy2 (+ iy1 2750.0))
    (_r (list sx1 sy1 0.0) (list sx2 sy2 0.0) "ИС_Штамп_Контур")
    (_l (list sx1 (+ sy1 750.0) 0.0) (list sx2 (+ sy1 750.0) 0.0) "ИС_Штамп_Контур")
    (_l (list sx1 (+ sy1 1750.0) 0.0) (list sx2 (+ sy1 1750.0) 0.0) "ИС_Штамп_Контур")
    (_l (list sx1 (+ sy1 2000.0) 0.0) (list (+ sx1 3250.0) (+ sy1 2000.0) 0.0) "ИС_Штамп_Тонкая")
    (_l (list sx1 (+ sy1 2250.0) 0.0) (list (+ sx1 3250.0) (+ sy1 2250.0) 0.0) "ИС_Штамп_Тонкая")
    (_l (list sx1 (+ sy1 2500.0) 0.0) (list (+ sx1 3250.0) (+ sy1 2500.0) 0.0) "ИС_Штамп_Тонкая")
    
    (_l (list (+ sx1 850.0) (+ sy1 750.0) 0.0) (list (+ sx1 850.0) sy2 0.0) "ИС_Штамп_Тонкая")
    (_l (list (+ sx1 1900.0) (+ sy1 750.0) 0.0) (list (+ sx1 1900.0) sy2 0.0) "ИС_Штамп_Тонкая")
    (_l (list (+ sx1 2650.0) (+ sy1 750.0) 0.0) (list (+ sx1 2650.0) sy2 0.0) "ИС_Штамп_Тонкая")
    (_l (list (+ sx1 3250.0) sy1 0.0) (list (+ sx1 3250.0) sy2 0.0) "ИС_Штамп_Контур")
    (_l (list (- sx2 2500.0) sy1 0.0) (list (- sx2 2500.0) (+ sy1 1750.0) 0.0) "ИС_Штамп_Контур")
    (_l (list (- sx2 1750.0) (+ sy1 750.0) 0.0) (list (- sx2 1750.0) (+ sy1 1750.0) 0.0) "ИС_Штамп_Тонкая")
    (_l (list (- sx2 1000.0) (+ sy1 750.0) 0.0) (list (- sx2 1000.0) (+ sy1 1750.0) 0.0) "ИС_Штамп_Тонкая")
    
    (_t "Разраб." (list (+ sx1 120.0) (+ sy1 2560.0) 0.0) 120.0 "ИС_Текст_Основной" "L")
    (_t "Ерышев М.С." (list (+ sx1 950.0) (+ sy1 2560.0) 0.0) 135.0 "ИС_Текст_Основной" "L")
    (_t "Пров." (list (+ sx1 120.0) (+ sy1 2310.0) 0.0) 120.0 "ИС_Текст_Основной" "L")
    (_t "ГИП" (list (+ sx1 120.0) (+ sy1 2060.0) 0.0) 120.0 "ИС_Текст_Основной" "L")
    (_t "Н.контр." (list (+ sx1 120.0) (+ sy1 1810.0) 0.0) 120.0 "ИС_Текст_Основной" "L")
    
    (_t "Сохранение ОКН: «Братская могила советских воинов, 1943 г.»"
        (list (+ sx1 3400.0) (+ sy1 2420.0) 0.0) 145.0 "ИС_Текст_Основной" "L")
    (_t "Белгородская обл., Корочанский р-н, с. Поповка, ул. Центральная"
        (list (+ sx1 3400.0) (+ sy1 2100.0) 0.0) 140.0 "ИС_Текст_Основной" "L")
    (_t s-title (list (+ sx1 3400.0) (+ sy1 1300.0) 0.0) 170.0 "ИС_Текст_Основной" "L")
    
    (_t "Стадия" (list (- sx2 2125.0) (+ sy1 1450.0) 0.0) 100.0 "ИС_Текст_Основной" "C")
    (_t "ИД" (list (- sx2 2125.0) (+ sy1 1050.0) 0.0) 150.0 "ИС_Текст_Основной" "C")
    (_t "Лист" (list (- sx2 1375.0) (+ sy1 1450.0) 0.0) 100.0 "ИС_Текст_Основной" "C")
    (_t (itoa s-num) (list (- sx2 1375.0) (+ sy1 1050.0) 0.0) 150.0 "ИС_Текст_Основной" "C")
    (_t "Листов" (list (- sx2 500.0) (+ sy1 1450.0) 0.0) 100.0 "ИС_Текст_Основной" "C")
    (_t "4" (list (- sx2 500.0) (+ sy1 1050.0) 0.0) 150.0 "ИС_Текст_Основной" "C")
    (_t "ООО «БМК»" (list (- sx2 1250.0) (+ sy1 320.0) 0.0) 220.0 "ИС_Текст_Основной" "C")
    
    (_r (list (- ix2 4000.0) (- iy2 900.0) 0.0) (list ix2 iy2 0.0) "ИС_Штамп_Контур")
    (_t "к АОСР № _____ от «____» __________ 2026 г." (list (- ix2 3850.0) (- iy2 550.0) 0.0) 135.0 "ИС_Текст_Основной" "L")
  )
    

  ;; Базовая координата Y для НОВЫХ исправленных схем
  (setq by_v2 -430000.0)
  (setq c_pts (list 700.0 2050.0 3400.0 4750.0 6100.0 7450.0 8950.0))

  ;; =========================================================================
  ;; ЛИСТ 1 (НОВЫЙ): ИС №1 — ДЕМОНТАЖ КОНСТРУКЦИЙ (ТОЧНЫЙ РЕДИЗАЙН 1 В 1)
  ;; =========================================================================
  (setq b1_x 400000.0 b1_y by_v2)
  (_frame b1_x b1_y 1 "Исполнительная схема. Демонтаж конструкций ограждения и фундаментов")

  (_t "Исполнительная схема №1" (list (+ b1_x 10500.0) (+ b1_y 14100.0) 0.0) 240.0 "ИС_Текст_Основной" "C")
  (_t "Демонтаж конструкций на объекте: \"Сохранение объекта культурного наследия регионального значения «Братская могила советских воинов,"
      (list (+ b1_x 10500.0) (+ b1_y 13700.0) 0.0) 140.0 "ИС_Текст_Основной" "C")
  (_t "погибших в боях с фашистскими захватчиками в 1943 году. Захоронено 38 человек, имена 3 человек установлены. Скульптура советского воина», 1967 г.,"
      (list (+ b1_x 10500.0) (+ b1_y 13400.0) 0.0) 130.0 "ИС_Текст_Основной" "C")
  (_t "Белгородская область, Корочанский район, село Поповка, улица Центральная\""
      (list (+ b1_x 10500.0) (+ b1_y 13100.0) 0.0) 130.0 "ИС_Текст_Основной" "C")

  (setq gnd_y (+ b1_y 7500.0))
  (setq fnd_y (- gnd_y 1200.0))
  (setq top_y (+ gnd_y 2650.0))

  ;; Уровни
  (_l (list (+ b1_x 1200.0) gnd_y 0.0) (list (+ b1_x 15500.0) gnd_y 0.0) "ИС_Тонкая")
  (_t "Уровень земли 0.000" (list (+ b1_x 15600.0) (+ gnd_y 350.0) 0.0) 130.0 "ИС_Текст_Основной" "L")
  (_l (list (+ b1_x 15800.0) (+ gnd_y 300.0) 0.0) (list (+ b1_x 15800.0) gnd_y 0.0) "ИС_Тонкая")

  (_l (list (+ b1_x 1200.0) fnd_y 0.0) (list (+ b1_x 14000.0) fnd_y 0.0) "ИС_Тонкая")
  (_t "Низ основания" (list (+ b1_x 9000.0) (- fnd_y 250.0) 0.0) 130.0 "ИС_Текст_Основной" "C")
  (_t "фундаментов -1.200" (list (+ b1_x 9000.0) (- fnd_y 450.0) 0.0) 130.0 "ИС_Текст_Основной" "C")
  (_l (list (+ b1_x 10100.0) (- fnd_y 400.0) 0.0) (list (+ b1_x 10100.0) fnd_y 0.0) "ИС_Тонкая")

  (_t "Верх демонтируемой" (list (+ b1_x 6500.0) (+ top_y 600.0) 0.0) 130.0 "ИС_Текст_Основной" "C")
  (_t "конструкции +2.650" (list (+ b1_x 6500.0) (+ top_y 400.0) 0.0) 130.0 "ИС_Текст_Основной" "C")
  (_l (list (+ b1_x 6500.0) (+ top_y 350.0) 0.0) (list (+ b1_x 6500.0) top_y 0.0) "ИС_Тонкая")

  ;; Функция отрисовки столба
  (defun _draw_demo_pillar (px pw)
    (_r (list px fnd_y 0.0) (list (+ px pw) gnd_y 0.0) "ИС_Демонтаж_Кладка")
    (_r (list px gnd_y 0.0) (list (+ px pw) top_y 0.0) "ИС_Демонтаж_Кладка")
    (_r (list (- (+ px (/ pw 2.0)) 25.0) gnd_y 0.0) (list (+ (+ px (/ pw 2.0)) 25.0) top_y 0.0) "ИС_Демонтаж_Металл")
    (setq pk_x (+ px (/ pw 2.0)) pk_y (+ top_y 550.0))
    (_l (list (- px 80.0) top_y 0.0) (list pk_x pk_y 0.0) "ИС_Демонтаж_Кладка")
    (_l (list (+ px pw 80.0) top_y 0.0) (list pk_x pk_y 0.0) "ИС_Демонтаж_Кладка")
    (_l (list (- px 80.0) top_y 0.0) (list (+ px pw 80.0) top_y 0.0) "ИС_Демонтаж_Кладка")
    (_l (list pk_x pk_y 0.0) (list pk_x top_y 0.0) "ИС_Тонкая")
  )

  ;; Функция отрисовки пролета
  (defun _draw_demo_span (sx sw)
    (setq st (+ gnd_y 2050.0))
    (_r (list sx gnd_y 0.0) (list (+ sx sw) st 0.0) "ИС_Демонтаж_Профлист")
    (_l (list sx (+ gnd_y 400.0) 0.0) (list (+ sx sw) (+ gnd_y 400.0) 0.0) "ИС_Демонтаж_Металл")
    (_l (list sx (+ gnd_y 1025.0) 0.0) (list (+ sx sw) (+ gnd_y 1025.0) 0.0) "ИС_Демонтаж_Металл")
    (_l (list sx (+ gnd_y 1800.0) 0.0) (list (+ sx sw) (+ gnd_y 1800.0) 0.0) "ИС_Демонтаж_Металл")
    (setq p_x (+ sx (/ sw 2.0)))
    (_r (list (- p_x 50.0) fnd_y 0.0) (list (+ p_x 50.0) top_y 0.0) "ИС_Демонтаж_Металл")
    (_r (list (- p_x 150.0) fnd_y 0.0) (list (+ p_x 150.0) gnd_y 0.0) "ИС_Демонтаж_Кладка")
  )

  (setq cur_x (+ b1_x 2200.0))
  ;; Столб 1 (640)
  (setq p1_x cur_x)
  (_draw_demo_pillar p1_x 640.0)
  (_t "Металлический" (list (+ p1_x 320.0) (+ top_y 1200.0) 0.0) 110.0 "ИС_Текст_Основной" "C")
  (_t "колпак из жести" (list (+ p1_x 320.0) (+ top_y 1050.0) 0.0) 110.0 "ИС_Текст_Основной" "C")
  (_l (list (+ p1_x 320.0) (+ top_y 1000.0) 0.0) (list (+ p1_x 320.0) (+ top_y 550.0) 0.0) "ИС_Тонкая")
  (setq cur_x (+ cur_x 640.0))

  ;; Пролет 1 (1450)
  (setq s1_x cur_x)
  (_draw_demo_span s1_x 1450.0)
  (setq cur_x (+ cur_x 1450.0))

  ;; Столб 2 (640)
  (setq p2_x cur_x)
  (_draw_demo_pillar p2_x 640.0)
  (setq cur_x (+ cur_x 640.0))

  ;; Пролет 2 (970)
  (setq s2_x cur_x)
  (_draw_demo_span s2_x 970.0)
  (_t "Профильная труба" (list (+ s2_x 485.0) (+ top_y 700.0) 0.0) 120.0 "ИС_Текст_Основной" "C")
  (_t "100*100" (list (+ s2_x 485.0) (+ top_y 520.0) 0.0) 120.0 "ИС_Текст_Основной" "C")
  (_l (list (+ s2_x 485.0) (+ top_y 480.0) 0.0) (list (+ s2_x 485.0) (+ top_y 50.0) 0.0) "ИС_Тонкая")
  (setq cur_x (+ cur_x 970.0))

  ;; Столб 3 (660)
  (setq p3_x cur_x)
  (_draw_demo_pillar p3_x 660.0)
  (setq cur_x (+ cur_x 660.0))

  ;; Пролет 3 (1030)
  (setq s3_x cur_x)
  (_draw_demo_span s3_x 1030.0)
  (_t "Проф труба 40*20*2" (list (+ s3_x 515.0) (+ top_y 800.0) 0.0) 120.0 "ИС_Текст_Основной" "C")
  (_l (list (+ s3_x 515.0) (+ top_y 750.0) 0.0) (list (+ s3_x 515.0) (+ gnd_y 1800.0) 0.0) "ИС_Тонкая")
  (_t "Фундаменты" (list (+ s3_x 515.0) (- fnd_y 650.0) 0.0) 120.0 "ИС_Текст_Основной" "C")
  (_t "профильных труб" (list (+ s3_x 515.0) (- fnd_y 820.0) 0.0) 120.0 "ИС_Текст_Основной" "C")
  (_t "Размер фундамента" (list (+ s3_x 515.0) (- fnd_y 1050.0) 0.0) 110.0 "ИС_Текст_Основной" "C")
  (_t "0,3*0,3*1,2" (list (+ s3_x 515.0) (- fnd_y 1220.0) 0.0) 110.0 "ИС_Текст_Основной" "C")
  (_l (list (+ s3_x 515.0) (- fnd_y 600.0) 0.0) (list (+ s3_x 515.0) (+ fnd_y 300.0) 0.0) "ИС_Тонкая")
  (setq cur_x (+ cur_x 1030.0))

  ;; Столб 4 (640)
  (setq p4_x cur_x)
  (_draw_demo_pillar p4_x 640.0)
  (setq cur_x (+ cur_x 640.0))

  ;; Боковой пролет (1450)
  (setq s4_x cur_x)
  (_draw_demo_span s4_x 1450.0)
  (setq cur_x (+ cur_x 1450.0))

  ;; Размерная линия внизу
  (setq dim_y (- fnd_y 350.0))
  (_l (list p1_x dim_y 0.0) (list cur_x dim_y 0.0) "ИС_Размеры")
  (setq d_list (list (list p1_x 640.0) (list s1_x 1450.0) (list p2_x 640.0) (list s2_x 970.0)
                     (list p3_x 660.0) (list s3_x 1030.0) (list p4_x 640.0) (list s4_x 1450.0)))
  (foreach item d_list
    (setq xs (car item) dw (cadr item))
    (_l (list xs (- dim_y 80.0) 0.0) (list xs (+ dim_y 80.0) 0.0) "ИС_Размеры")
    (_t (rtos dw 2 0) (list (+ xs (/ dw 2.0)) (- dim_y 220.0) 0.0) 120.0 "ИС_Размеры" "C")
  )
  (_l (list cur_x (- dim_y 80.0) 0.0) (list cur_x (+ dim_y 80.0) 0.0) "ИС_Размеры")

  ;; Аксонометрический узел каркаса (вверху справа)
  (setq iso_x (+ b1_x 16200.0) iso_y (+ b1_y 9500.0))
  (_t "Каркас обшивки" (list (+ iso_x 600.0) (+ iso_y 3200.0) 0.0) 140.0 "ИС_Текст_Основной" "C")
  (_t "кладки проф трубой" (list (+ iso_x 600.0) (+ iso_y 3000.0) 0.0) 140.0 "ИС_Текст_Основной" "C")
  (_t "40*20*2" (list (+ iso_x 600.0) (+ iso_y 2800.0) 0.0) 140.0 "ИС_Текст_Основной" "C")

  (_r (list iso_x iso_y 0.0) (list (+ iso_x 600.0) (+ iso_y 2400.0) 0.0) "ИС_Контур_Толстый")
  (_l (list iso_x (+ iso_y 800.0) 0.0) (list (+ iso_x 600.0) (+ iso_y 800.0) 0.0) "ИС_Демонтаж_Металл")
  (_l (list iso_x (+ iso_y 1600.0) 0.0) (list (+ iso_x 600.0) (+ iso_y 1600.0) 0.0) "ИС_Демонтаж_Металл")
  (setq dx_iso 400.0 dy_iso 400.0)
  (_r (list (+ iso_x dx_iso) (+ iso_y dy_iso) 0.0) (list (+ iso_x 600.0 dx_iso) (+ iso_y 2400.0 dy_iso) 0.0) "ИС_Тонкая")
  (_l (list iso_x iso_y 0.0) (list (+ iso_x dx_iso) (+ iso_y dy_iso) 0.0) "ИС_Тонкая")
  (_l (list (+ iso_x 600.0) iso_y 0.0) (list (+ iso_x 600.0 dx_iso) (+ iso_y dy_iso) 0.0) "ИС_Контур_Толстый")
  (_l (list (+ iso_x 600.0) (+ iso_y 2400.0) 0.0) (list (+ iso_x 600.0 dx_iso) (+ iso_y 2400.0 dy_iso) 0.0) "ИС_Контур_Толстый")
  (_l (list iso_x (+ iso_y 2400.0) 0.0) (list (+ iso_x dx_iso) (+ iso_y 2400.0 dy_iso) 0.0) "ИС_Контур_Толстый")
  (_l (list (+ iso_x 600.0) (+ iso_y 800.0) 0.0) (list (+ iso_x 600.0 dx_iso) (+ iso_y 800.0 dy_iso) 0.0) "ИС_Демонтаж_Металл")
  (_l (list (+ iso_x 600.0) (+ iso_y 1600.0) 0.0) (list (+ iso_x 600.0 dx_iso) (+ iso_y 1600.0 dy_iso) 0.0) "ИС_Демонтаж_Металл")

  (_t "Кладка обшита металлическим каркасом из проф" (list (- iso_x 300.0) (- iso_y 300.0) 0.0) 110.0 "ИС_Текст_Основной" "L")
  (_t "трубы 40*20*2 (каркас схематично показан)" (list (- iso_x 300.0) (- iso_y 480.0) 0.0) 110.0 "ИС_Текст_Основной" "L")

  ;; 3 Блока формул и расчетов внизу
  (setq calc_y (+ b1_y 4200.0))
  (setq c1_x (+ b1_x 1200.0))
  (_t "Итого демонтаж фундамента: (0,64*1,45*1,2)+(0,64*0,97*" (list c1_x calc_y 0.0) 120.0 "ИС_Текст_Основной" "L")
  (_t "1,2)+(0,66*1,03*1,2)+(0,64*1,45*1,2) + (0,3*0,3*1,2)*3шт = 4,087м3" (list c1_x (- calc_y 200.0) 0.0) 120.0 "ИС_Текст_Основной" "L")
  (_t "Итого демонтаж кладки: (1,45*0,64*2,65)+(0,97*0,64*2,65)+" (list c1_x (- calc_y 500.0) 0.0) 120.0 "ИС_Текст_Основной" "L")
  (_t "(1,03*0,64*2,65)+(1,45*0,64*2,65) = 8.31 м3" (list c1_x (- calc_y 700.0) 0.0) 120.0 "ИС_Текст_Основной" "L")
  (_t "Итого вывоз демонтируемых фундаментов и кладки:" (list c1_x (- calc_y 1000.0) 0.0) 120.0 "ИС_Текст_Основной" "L")
  (_t "4,087м3 + 8.31 м3 = 12,397м3 * 2000кг (удельный вес кладки) = 24 794кг" (list c1_x (- calc_y 1200.0) 0.0) 120.0 "ИС_Текст_Основной" "L")

  (setq c2_x (+ b1_x 7600.0))
  (_t "Итого металлических конструкций демонтировано:" (list c2_x (+ calc_y 250.0) 0.0) 125.0 "ИС_Текст_Основной" "L")
  (_t "1)Проф труба для обшивки кладки 40*20*2 = (0,64*8+1,45*8+2,65*8)+" (list c2_x calc_y 0.0) 115.0 "ИС_Текст_Основной" "L")
  (_t "(0,64*8+0,97*8+2,65*8)+(0,66*8+1,03*8+2,65*8)+(0,64*8+1,45*8+2,65*8) = 144,64м.п." (list c2_x (- calc_y 200.0) 0.0) 115.0 "ИС_Текст_Основной" "L")
  (_t "2)Проф труба 40*20*2 между кладкой = 3,48*3+5,72*3+3,56*3 = 38,28 м.п." (list c2_x (- calc_y 450.0) 0.0) 115.0 "ИС_Текст_Основной" "L")
  (_t "Итого проф труба 40*20*2 = 144,64+38,28 = 182,92 м.п." (list c2_x (- calc_y 650.0) 0.0) 115.0 "ИС_Текст_Основной" "L")
  (_t "Вывоз демонтируемой проф трубы 40*20*2 = 182,92 * 1,7 кг = 310,96кг" (list c2_x (- calc_y 850.0) 0.0) 115.0 "ИС_Текст_Основной" "L")
  (_t "3)Проф труба 100*100*3 = (2,65+1,2)*3шт = 11,55 м.п. * 9кг = 103,95 кг" (list c2_x (- calc_y 1100.0) 0.0) 115.0 "ИС_Текст_Основной" "L")
  (_t "Всего металлический конструкций демонтировано = 310,96+103,95 = 414,91кг" (list c2_x (- calc_y 1300.0) 0.0) 125.0 "ИС_Текст_Основной" "L")

  (setq c3_x (+ b1_x 14000.0))
  (_t "Демонтаж проф листа с колонн: (1,45*2,65)*2 стороны+(0,64*2,65)*2 стороны+" (list c3_x (+ calc_y 250.0) 0.0) 110.0 "ИС_Текст_Основной" "L")
  (_t "(0,97*2,65)*2 стороны+(0,64*2,65)*2 стороны+(1,03*2,65)*2 стороны+(0,66*2,65)*2 стороны+" (list c3_x (+ calc_y 50.0) 0.0) 110.0 "ИС_Текст_Основной" "L")
  (_t "(1,45*2,65)*2 стороны+(0,64*2,65)*2 стороны = 39,644 м2" (list c3_x (- calc_y 150.0) 0.0) 110.0 "ИС_Текст_Основной" "L")
  (_t "Демонтаж проф листа между колоннами: (3,48+5,72+3,56)*2,05 = 21,158 м2" (list c3_x (- calc_y 400.0) 0.0) 110.0 "ИС_Текст_Основной" "L")
  (_t "Итого демонтаж проф листа: 21,158+39,644 = 60,8м2." (list c3_x (- calc_y 650.0) 0.0) 115.0 "ИС_Текст_Основной" "L")
  (_t "Вывоз демонтируемого проф листа = 60,8м2 * 4,7 кг = 285,76кг" (list c3_x (- calc_y 850.0) 0.0) 115.0 "ИС_Текст_Основной" "L")

  (_t "ОБЩАЯ МАССА ДЕМОНТАЖА К ВЫВОЗУ: 24794 + 414,91 + 285,76 = 25 494,67 кг (~25,5 т)"
      (list (+ b1_x 1200.0) (+ b1_y 2400.0) 0.0) 150.0 "ИС_Текст_Основной" "L")

  ;; =========================================================================
  ;; ЛИСТ 2 (НОВЫЙ): РАЗРАБОТКА ГРУНТА
  ;; =========================================================================
  (setq b2_x 424000.0 b2_y by_v2)
  (_frame b2_x b2_y 2 "Исполнительная схема. Разработка грунта и бурение скважин")

  (_t "ИСПОЛНИТЕЛЬНАЯ СХЕМА №2" (list (+ b2_x 10500.0) (+ b2_y 14000.0) 0.0) 240.0 "ИС_Текст_Основной" "C")
  (_t "Разработка грунта траншеи и бурение скважин под буронабивные сваи"
      (list (+ b2_x 10500.0) (+ b2_y 13500.0) 0.0) 170.0 "ИС_Текст_Основной" "C")

  (setq pl2_x (+ b2_x 1500.0) pl2_y (+ b2_y 10200.0))
  (_t "ПЛАН ТРАНШЕИ И ТОЧЕК БУРЕНИЯ СКВАЖИН (М 1:50)" (list pl2_x (+ pl2_y 1600.0) 0.0) 160.0 "ИС_Текст_Основной" "L")

  ;; Полилиния контура траншеи
  (_l (list pl2_x pl2_y 0.0) (list (+ pl2_x 9650.0) pl2_y 0.0) "ИС_Контур_Толстый")
  (_l (list (+ pl2_x 9650.0) pl2_y 0.0) (list (+ pl2_x 9650.0) (- pl2_y 750.0) 0.0) "ИС_Контур_Толстый")
  (_l (list (+ pl2_x 9650.0) (- pl2_y 750.0) 0.0) (list (+ pl2_x 8650.0) (- pl2_y 750.0) 0.0) "ИС_Контур_Толстый")
  (_l (list (+ pl2_x 8650.0) (- pl2_y 750.0) 0.0) (list (+ pl2_x 8650.0) (- pl2_y 600.0) 0.0) "ИС_Контур_Толстый")
  (_l (list (+ pl2_x 8650.0) (- pl2_y 600.0) 0.0) (list (+ pl2_x 6250.0) (- pl2_y 600.0) 0.0) "ИС_Контур_Толстый")
  (_l (list (+ pl2_x 6250.0) (- pl2_y 600.0) 0.0) (list (+ pl2_x 6250.0) (- pl2_y 500.0) 0.0) "ИС_Контур_Толстый")
  (_l (list (+ pl2_x 6250.0) (- pl2_y 500.0) 0.0) (list (+ pl2_x 4400.0) (- pl2_y 500.0) 0.0) "ИС_Контур_Толстый")
  (_l (list (+ pl2_x 4400.0) (- pl2_y 500.0) 0.0) (list (+ pl2_x 4400.0) (- pl2_y 600.0) 0.0) "ИС_Контур_Толстый")
  (_l (list (+ pl2_x 4400.0) (- pl2_y 600.0) 0.0) (list (+ pl2_x 2050.0) (- pl2_y 600.0) 0.0) "ИС_Контур_Толстый")
  (_l (list (+ pl2_x 2050.0) (- pl2_y 600.0) 0.0) (list (+ pl2_x 2050.0) (- pl2_y 700.0) 0.0) "ИС_Контур_Толстый")
  (_l (list (+ pl2_x 2050.0) (- pl2_y 700.0) 0.0) (list pl2_x (- pl2_y 700.0) 0.0) "ИС_Контур_Толстый")
  (_l (list pl2_x (- pl2_y 700.0) 0.0) (list pl2_x pl2_y 0.0) "ИС_Контур_Толстый")

  (foreach cx c_pts
    (setq sc_x (+ pl2_x cx) sc_y (- pl2_y 320.0))
    (_c (list sc_x sc_y 0.0) 100.0 "ИС_Контур_Толстый")
    (_l (list (- sc_x 160.0) sc_y 0.0) (list (+ sc_x 160.0) sc_y 0.0) "ИС_Оси")
    (_l (list sc_x (- sc_y 160.0) 0.0) (list sc_x (+ sc_y 160.0) 0.0) "ИС_Оси")
  )

  (_l (list pl2_x (+ pl2_y 350.0) 0.0) (list (+ pl2_x 9650.0) (+ pl2_y 350.0) 0.0) "ИС_Размеры")
  (_t "9650" (list (+ pl2_x 4825.0) (+ pl2_y 480.0) 0.0) 140.0 "ИС_Размеры" "C")
  (_t "Скважины d=200 мм (7 шт., глубина 0.65 м от дна траншеи)" (list (+ pl2_x 700.0) (- pl2_y 1100.0) 0.0) 125.0 "ИС_Текст_Основной" "L")

  ;; Разрез 1-1
  (setq sc2_x (+ b2_x 1500.0) sc2_y (+ b2_y 5800.0))
  (_t "ПРОДОЛЬНЫЙ РАЗРЕЗ 1-1 (ПО ОСИ ТРАНШЕИ И СКВАЖИН)" (list sc2_x (+ sc2_y 1300.0) 0.0) 160.0 "ИС_Текст_Основной" "L")
  (_l (list (- sc2_x 300.0) sc2_y 0.0) (list (+ sc2_x 10000.0) sc2_y 0.0) "ИС_Оси")
  (_t "? 0.000 (Уровень земли)" (list (+ sc2_x 10100.0) sc2_y 0.0) 130.0 "ИС_Текст_Основной" "L")

  (setq btm2_y (- sc2_y 700.0))
  (_l (list sc2_x btm2_y 0.0) (list (+ sc2_x 9650.0) btm2_y 0.0) "ИС_Контур_Толстый")
  (_t "? -0.700 (Дно траншеи)" (list (+ sc2_x 10100.0) btm2_y 0.0) 130.0 "ИС_Текст_Основной" "L")

  (setq snd2_y (- sc2_y 600.0))
  (_l (list sc2_x snd2_y 0.0) (list (+ sc2_x 9650.0) snd2_y 0.0) "ИС_Тонкая")
  (_t "? -0.600 (Песчаная подготовка h=100мм)" (list (+ sc2_x 10100.0) snd2_y 0.0) 130.0 "ИС_Текст_Основной" "L")
  (_l (list sc2_x sc2_y 0.0) (list sc2_x btm2_y 0.0) "ИС_Контур_Толстый")
  (_l (list (+ sc2_x 9650.0) sc2_y 0.0) (list (+ sc2_x 9650.0) btm2_y 0.0) "ИС_Контур_Толстый")

  (setq pile_btm2_y (- btm2_y 650.0))
  (_t "? -1.350 (Забой бурения скважин)" (list (+ sc2_x 10100.0) pile_btm2_y 0.0) 130.0 "ИС_Текст_Основной" "L")
  (foreach cx c_pts
    (setq px (+ sc2_x cx))
    (_l (list (- px 100.0) snd2_y 0.0) (list (- px 100.0) pile_btm2_y 0.0) "ИС_Контур_Толстый")
    (_l (list (+ px 100.0) snd2_y 0.0) (list (+ px 100.0) pile_btm2_y 0.0) "ИС_Контур_Толстый")
    (_l (list (- px 100.0) pile_btm2_y 0.0) (list (+ px 100.0) pile_btm2_y 0.0) "ИС_Контур_Толстый")
  )

  ;; Таблица земляных работ
  (setq tbl2_x (+ b2_x 11800.0) tbl2_y (+ b2_y 12800.0) tbl2_w 8800.0)
  (_t "ВЕДОМОСТЬ ОБЪЕМОВ ЗЕМЛЯНЫХ РАБОТ" (list (+ tbl2_x 4400.0) (+ tbl2_y 350.0) 0.0) 170.0 "ИС_Текст_Основной" "C")
  (_r (list tbl2_x (- tbl2_y 5600.0) 0.0) (list (+ tbl2_x tbl2_w) tbl2_y 0.0) "ИС_Таблицы_Сетка")
  (_l (list tbl2_x (- tbl2_y 700.0) 0.0) (list (+ tbl2_x tbl2_w) (- tbl2_y 700.0) 0.0) "ИС_Таблицы_Сетка")
  (_t "№" (list (+ tbl2_x 300.0) (- tbl2_y 450.0) 0.0) 125.0 "ИС_Текст_Основной" "C")
  (_t "Наименование видов работ" (list (+ tbl2_x 3000.0) (- tbl2_y 450.0) 0.0) 125.0 "ИС_Текст_Основной" "C")
  (_t "Ед." (list (+ tbl2_x 5500.0) (- tbl2_y 450.0) 0.0) 125.0 "ИС_Текст_Основной" "C")
  (_t "Объем" (list (+ tbl2_x 6500.0) (- tbl2_y 450.0) 0.0) 125.0 "ИС_Текст_Основной" "C")
  (_t "Примечание" (list (+ tbl2_x 7700.0) (- tbl2_y 450.0) 0.0) 125.0 "ИС_Текст_Основной" "C")
  (foreach vx (list 600.0 5100.0 5900.0 7100.0)
    (_l (list (+ tbl2_x vx) (- tbl2_y 5600.0) 0.0) (list (+ tbl2_x vx) tbl2_y 0.0) "ИС_Таблицы_Сетка")
  )
  (setq rows2 '(
    ("1" "Механизированная разработка грунта в траншее" "м3" "3.75" "Экскаватор-погрузчик")
    ("2" "Доработка грунта вручную и подчистка дна" "м3" "0.45" "Вручную до отм. -0.700")
    ("3" "ИТОГО разработка грунта траншеи" "м3" "4.20" "Грунт II группы")
    ("4" "Бурение цилиндрических скважин d=200 мм" "м3" "0.143" "7 скважин h=0.65м")
    ("5" "Устройство песчаной подготовки h=100 мм" "м3" "0.62" "Песок ср., Купл=0.95")
    ("6" "Обратная засыпка пазух траншеи с уплотнением" "м3" "0.80" "Вручную с трамбованием")
    ("7" "Вывоз излишков разработанного грунта" "м3" "3.54" "Самосвалами в отвал")
  ))
  (setq cur_ry (- tbl2_y 700.0))
  (foreach r rows2
    (setq cur_ry (- cur_ry 700.0))
    (_l (list tbl2_x cur_ry 0.0) (list (+ tbl2_x tbl2_w) cur_ry 0.0) "ИС_Таблицы_Тонкая")
    (_t (nth 0 r) (list (+ tbl2_x 300.0) (+ cur_ry 230.0) 0.0) 120.0 "ИС_Текст_Основной" "C")
    (_t (nth 1 r) (list (+ tbl2_x 700.0) (+ cur_ry 230.0) 0.0) 120.0 "ИС_Текст_Основной" "L")
    (_t (nth 2 r) (list (+ tbl2_x 5500.0) (+ cur_ry 230.0) 0.0) 120.0 "ИС_Текст_Основной" "C")
    (_t (nth 3 r) (list (+ tbl2_x 6500.0) (+ cur_ry 230.0) 0.0) 120.0 "ИС_Текст_Основной" "C")
    (_t (nth 4 r) (list (+ tbl2_x 7300.0) (+ cur_ry 230.0) 0.0) 110.0 "ИС_Текст_Основной" "L")
  )

  ;; =========================================================================
  ;; ЛИСТ 3 (НОВЫЙ): АРМИРОВАНИЕ (ШАГ ХОМУТОВ 700 ММ)
  ;; =========================================================================
  (setq b3_x 448000.0 b3_y by_v2)
  (_frame b3_x b3_y 3 "Исполнительная схема. Армирование ленточного фундамента и буронабивных свай")

  (_t "ИСПОЛНИТЕЛЬНАЯ СХЕМА №3" (list (+ b3_x 10500.0) (+ b3_y 14000.0) 0.0) 240.0 "ИС_Текст_Основной" "C")
  (_t "Армирование монолитного ленточного ростверка и буронабивных свай"
      (list (+ b3_x 10500.0) (+ b3_y 13500.0) 0.0) 170.0 "ИС_Текст_Основной" "C")

  (setq pl3_x (+ b3_x 1500.0) pl3_y (+ b3_y 10200.0))
  (_t "ПЛАН АРМИРОВАНИЯ РОСТВЕРКА И ЗАКЛАДНЫХ ДЕТАЛЕЙ (М 1:50)" (list pl3_x (+ pl3_y 1600.0) 0.0) 160.0 "ИС_Текст_Основной" "L")
  (_r (list pl3_x (- pl3_y 600.0) 0.0) (list (+ pl3_x 9650.0) pl3_y 0.0) "ИС_Тонкая")

  (_l (list (+ pl3_x 50.0) (- pl3_y 50.0) 0.0) (list (+ pl3_x 9600.0) (- pl3_y 50.0) 0.0) "ИС_Арматура_Рабочая")
  (_l (list (+ pl3_x 50.0) (- pl3_y 300.0) 0.0) (list (+ pl3_x 9600.0) (- pl3_y 300.0) 0.0) "ИС_Арматура_Рабочая")
  (_l (list (+ pl3_x 50.0) (- pl3_y 550.0) 0.0) (list (+ pl3_x 9600.0) (- pl3_y 550.0) 0.0) "ИС_Арматура_Рабочая")

  (setq hx 100.0)
  (while (<= hx 9550.0)
    (_l (list (+ pl3_x hx) (- pl3_y 40.0) 0.0) (list (+ pl3_x hx) (- pl3_y 560.0) 0.0) "ИС_Арматура_Хомуты")
    (setq hx (+ hx 700.0))
  )

  (foreach cx c_pts
    (setq zx (+ pl3_x cx))
    (_r (list (- zx 100.0) (- pl3_y 400.0) 0.0) (list (+ zx 100.0) (- pl3_y 200.0) 0.0) "ИС_Контур_Толстый")
    (_c (list zx (- pl3_y 300.0) 0.0) 100.0 "ИС_Тонкая")
  )

  (_t "Закладная деталь ЗД-1: лист 200х200х8 с анкерами 4d12 А500С" (list (+ pl3_x 3000.0) (+ pl3_y 400.0) 0.0) 130.0 "ИС_Текст_Основной" "L")
  (_t "Поперечные прямоугольные хомуты d8 А240 с шагом 700 мм (по факту)" (list (+ pl3_x 3000.0) (- pl3_y 850.0) 0.0) 130.0 "ИС_Текст_Основной" "L")

  ;; Разрез армирования
  (setq sc3_x (+ b3_x 1500.0) sc3_y (+ b3_y 5800.0))
  (_t "ПРОДОЛЬНЫЙ РАЗРЕЗ 1-1 (КАРКАС РОСТВЕРКА И КАРКАСЫ СВАЙ)" (list sc3_x (+ sc3_y 1300.0) 0.0) 160.0 "ИС_Текст_Основной" "L")
  (_r (list sc3_x (- sc3_y 600.0) 0.0) (list (+ sc3_x 9650.0) sc3_y 0.0) "ИС_Тонкая")
  (_l (list (+ sc3_x 40.0) (- sc3_y 40.0) 0.0) (list (+ sc3_x 9610.0) (- sc3_y 40.0) 0.0) "ИС_Арматура_Рабочая")
  (_l (list (+ sc3_x 40.0) (- sc3_y 560.0) 0.0) (list (+ sc3_x 9610.0) (- sc3_y 560.0) 0.0) "ИС_Арматура_Рабочая")
  (_l (list (+ sc3_x 40.0) (- sc3_y 40.0) 0.0) (list (+ sc3_x 40.0) (- sc3_y 560.0) 0.0) "ИС_Арматура_Рабочая")
  (_l (list (+ sc3_x 9610.0) (- sc3_y 40.0) 0.0) (list (+ sc3_x 9610.0) (- sc3_y 560.0) 0.0) "ИС_Арматура_Рабочая")

  (setq hx 100.0)
  (while (<= hx 9550.0)
    (_l (list (+ sc3_x hx) (- sc3_y 40.0) 0.0) (list (+ sc3_x hx) (- sc3_y 560.0) 0.0) "ИС_Арматура_Хомуты")
    (setq hx (+ hx 700.0))
  )

  (foreach cx c_pts
    (setq px (+ sc3_x cx))
    (_r (list (- px 100.0) (- sc3_y 1250.0) 0.0) (list (+ px 100.0) (- sc3_y 600.0) 0.0) "ИС_Тонкая")
    (_l (list (- px 60.0) (- sc3_y 150.0) 0.0) (list (- px 60.0) (- sc3_y 1210.0) 0.0) "ИС_Арматура_Рабочая")
    (_l (list (+ px 60.0) (- sc3_y 150.0) 0.0) (list (+ px 60.0) (- sc3_y 1210.0) 0.0) "ИС_Арматура_Рабочая")
    (_l (list (- px 60.0) (- sc3_y 150.0) 0.0) (list (- px 150.0) (- sc3_y 150.0) 0.0) "ИС_Арматура_Рабочая")
    (_l (list (+ px 60.0) (- sc3_y 150.0) 0.0) (list (+ px 150.0) (- sc3_y 150.0) 0.0) "ИС_Арматура_Рабочая")
    (_r (list (- px 100.0) (- sc3_y 10.0) 0.0) (list (+ px 100.0) sc3_y 0.0) "ИС_Контур_Толстый")
  )

  ;; Спецификация арматуры
  (setq tbl3_x (+ b3_x 11800.0) tbl3_y (+ b3_y 12800.0) tbl3_w 8800.0)
  (_t "СПЕЦИФИКАЦИЯ АРМАТУРНЫХ И ЗАКЛАДНЫХ ИЗДЕЛИЙ" (list (+ tbl3_x 4400.0) (+ tbl3_y 350.0) 0.0) 170.0 "ИС_Текст_Основной" "C")
  (_r (list tbl3_x (- tbl3_y 7700.0) 0.0) (list (+ tbl3_x tbl3_w) tbl3_y 0.0) "ИС_Таблицы_Сетка")
  (_l (list tbl3_x (- tbl3_y 700.0) 0.0) (list (+ tbl3_x tbl3_w) (- tbl3_y 700.0) 0.0) "ИС_Таблицы_Сетка")
  (_t "Поз." (list (+ tbl3_x 300.0) (- tbl3_y 450.0) 0.0) 120.0 "ИС_Текст_Основной" "C")
  (_t "Наименование / Диаметр" (list (+ tbl3_x 2600.0) (- tbl3_y 450.0) 0.0) 120.0 "ИС_Текст_Основной" "C")
  (_t "Кол." (list (+ tbl3_x 4900.0) (- tbl3_y 450.0) 0.0) 120.0 "ИС_Текст_Основной" "C")
  (_t "Длина, м" (list (+ tbl3_x 5700.0) (- tbl3_y 450.0) 0.0) 120.0 "ИС_Текст_Основной" "C")
  (_t "Общ.дл, м" (list (+ tbl3_x 6600.0) (- tbl3_y 450.0) 0.0) 120.0 "ИС_Текст_Основной" "C")
  (_t "Масса, кг" (list (+ tbl3_x 7700.0) (- tbl3_y 450.0) 0.0) 120.0 "ИС_Текст_Основной" "C")
  (foreach vx (list 600.0 4600.0 5200.0 6200.0 7100.0)
    (_l (list (+ tbl3_x vx) (- tbl3_y 7700.0) 0.0) (list (+ tbl3_x vx) tbl3_y 0.0) "ИС_Таблицы_Сетка")
  )
  (setq rows3 '(
    ("1" "d12 А500С (продольная арматура ростверка)" "6" "9.85" "59.10" "52.48")
    ("2" "d8 А240 (хомуты ростверка, шаг 700 мм)" "15" "2.00" "30.00" "11.85")
    ("3" "d12 А500С (стержни каркасов свай КП-1)" "28" "1.10" "30.80" "27.35")
    ("4" "d6 А240 (хомуты каркасов свай КП-1)" "28" "0.55" "15.40" "3.42")
    ("5" "Лист -200х200х8 (пластина ЗД-1)" "7" "—" "—" "17.58")
    ("6" "d12 А500С (анкеры детали ЗД-1, l=400)" "28" "0.40" "11.20" "9.95")
    ("ИТОГО" "Арматура класса А500С (ГОСТ 34028-2016)" "—" "—" "101.10" "89.78")
    ("ИТОГО" "Арматура класса А240 (ГОСТ 34028-2016)" "—" "—" "45.40" "15.27")
    ("ИТОГО" "Сталь прокатная листовая (ГОСТ 19903-2015)" "—" "—" "—" "17.58")
    ("ВСЕГО" "РАСХОД СТАЛИ НА ОБЪЕКТ" "—" "—" "—" "122.63")
  ))
  (setq cur_ry (- tbl3_y 700.0))
  (foreach r rows3
    (setq cur_ry (- cur_ry 700.0))
    (_l (list tbl3_x cur_ry 0.0) (list (+ tbl3_x tbl3_w) cur_ry 0.0) "ИС_Таблицы_Тонкая")
    (_t (nth 0 r) (list (+ tbl3_x 300.0) (+ cur_ry 230.0) 0.0) 120.0 "ИС_Текст_Основной" "C")
    (_t (nth 1 r) (list (+ tbl3_x 700.0) (+ cur_ry 230.0) 0.0) 120.0 "ИС_Текст_Основной" "L")
    (_t (nth 2 r) (list (+ tbl3_x 4900.0) (+ cur_ry 230.0) 0.0) 120.0 "ИС_Текст_Основной" "C")
    (_t (nth 3 r) (list (+ tbl3_x 5700.0) (+ cur_ry 230.0) 0.0) 120.0 "ИС_Текст_Основной" "C")
    (_t (nth 4 r) (list (+ tbl3_x 6600.0) (+ cur_ry 230.0) 0.0) 120.0 "ИС_Текст_Основной" "C")
    (_t (nth 5 r) (list (+ tbl3_x 7700.0) (+ cur_ry 230.0) 0.0) 120.0 "ИС_Текст_Основной" "C")
  )

  ;; =========================================================================
  ;; ЛИСТ 4 (НОВЫЙ): БЕТОНИРОВАНИЕ
  ;; =========================================================================
  (setq b4_x 472000.0 b4_y by_v2)
  (_frame b4_x b4_y 4 "Исполнительная схема. Бетонирование ленточного фундамента и буронабивных свай")

  (_t "ИСПОЛНИТЕЛЬНАЯ СХЕМА №4" (list (+ b4_x 10500.0) (+ b4_y 14000.0) 0.0) 240.0 "ИС_Текст_Основной" "C")
  (_t "Бетонирование монолитного ленточного ростверка и буронабивных свай"
      (list (+ b4_x 10500.0) (+ b4_y 13500.0) 0.0) 170.0 "ИС_Текст_Основной" "C")

  (setq pl4_x (+ b4_x 1500.0) pl4_y (+ b4_y 10200.0))
  (_t "ПЛАН МОНОЛИТНОГО РОСТВЕРКА И СВАЙ (ВИД СВЕРХУ)" (list pl4_x (+ pl4_y 1600.0) 0.0) 160.0 "ИС_Текст_Основной" "L")

  (_l (list pl4_x pl4_y 0.0) (list (+ pl4_x 9650.0) pl4_y 0.0) "ИС_Бетон_Контур")
  (_l (list (+ pl4_x 9650.0) pl4_y 0.0) (list (+ pl4_x 9650.0) (- pl4_y 750.0) 0.0) "ИС_Бетон_Контур")
  (_l (list (+ pl4_x 9650.0) (- pl4_y 750.0) 0.0) (list (+ pl4_x 8650.0) (- pl4_y 750.0) 0.0) "ИС_Бетон_Контур")
  (_l (list (+ pl4_x 8650.0) (- pl4_y 750.0) 0.0) (list (+ pl4_x 8650.0) (- pl4_y 600.0) 0.0) "ИС_Бетон_Контур")
  (_l (list (+ pl4_x 8650.0) (- pl4_y 600.0) 0.0) (list (+ pl4_x 6250.0) (- pl4_y 600.0) 0.0) "ИС_Бетон_Контур")
  (_l (list (+ pl4_x 6250.0) (- pl4_y 600.0) 0.0) (list (+ pl4_x 6250.0) (- pl4_y 500.0) 0.0) "ИС_Бетон_Контур")
  (_l (list (+ pl4_x 6250.0) (- pl4_y 500.0) 0.0) (list (+ pl4_x 4400.0) (- pl4_y 500.0) 0.0) "ИС_Бетон_Контур")
  (_l (list (+ pl4_x 4400.0) (- pl4_y 500.0) 0.0) (list (+ pl4_x 4400.0) (- pl4_y 600.0) 0.0) "ИС_Бетон_Контур")
  (_l (list (+ pl4_x 4400.0) (- pl4_y 600.0) 0.0) (list (+ pl4_x 2050.0) (- pl4_y 600.0) 0.0) "ИС_Бетон_Контур")
  (_l (list (+ pl4_x 2050.0) (- pl4_y 600.0) 0.0) (list (+ pl4_x 2050.0) (- pl4_y 700.0) 0.0) "ИС_Бетон_Контур")
  (_l (list (+ pl4_x 2050.0) (- pl4_y 700.0) 0.0) (list pl4_x (- pl4_y 700.0) 0.0) "ИС_Бетон_Контур")
  (_l (list pl4_x (- pl4_y 700.0) 0.0) (list pl4_x pl4_y 0.0) "ИС_Бетон_Контур")

  (foreach cx c_pts
    (setq sc_x (+ pl4_x cx) sc_y (- pl4_y 320.0))
    (_c (list sc_x sc_y 0.0) 100.0 "ИС_Тонкая")
  )

  (_l (list pl4_x (+ pl4_y 350.0) 0.0) (list (+ pl4_x 9650.0) (+ pl4_y 350.0) 0.0) "ИС_Размеры")
  (_t "9650" (list (+ pl4_x 4825.0) (+ pl4_y 480.0) 0.0) 140.0 "ИС_Размеры" "C")

  ;; Вид сбоку
  (setq sc4_x (+ b4_x 1500.0) sc4_y (+ b4_y 5800.0))
  (_t "ВИД СБОКУ (ФАСАД МОНОЛИТНОЙ КОНСТРУКЦИИ)" (list sc4_x (+ sc4_y 1300.0) 0.0) 160.0 "ИС_Текст_Основной" "L")
  (_r (list sc4_x (- sc4_y 600.0) 0.0) (list (+ sc4_x 9650.0) sc4_y 0.0) "ИС_Бетон_Контур")

  (foreach cx c_pts
    (setq px (+ sc4_x cx))
    (_r (list (- px 100.0) (- sc4_y 1250.0) 0.0) (list (+ px 100.0) (- sc4_y 600.0) 0.0) "ИС_Бетон_Контур")
  )

  (_l (list (- sc4_x 300.0) sc4_y 0.0) (list (+ sc4_x 10000.0) sc4_y 0.0) "ИС_Оси")
  (_t "? +0.100 (Верх ростверка)" (list (+ sc4_x 10100.0) sc4_y 0.0) 130.0 "ИС_Текст_Основной" "L")
  (_t "? 0.000 (Уровень земли)" (list (+ sc4_x 10100.0) (- sc4_y 100.0) 0.0) 130.0 "ИС_Текст_Основной" "L")
  (_t "? -0.500 (Низ ростверка)" (list (+ sc4_x 10100.0) (- sc4_y 600.0) 0.0) 130.0 "ИС_Текст_Основной" "L")
  (_t "? -1.150 (Низ свай)" (list (+ sc4_x 10100.0) (- sc4_y 1250.0) 0.0) 130.0 "ИС_Текст_Основной" "L")

  ;; Таблица бетонирования
  (setq tbl4_x (+ b4_x 11800.0) tbl4_y (+ b4_y 12800.0) tbl4_w 8800.0)
  (_t "ВЕДОМОСТЬ ОБЪЕМОВ БЕТОННЫХ РАБОТ" (list (+ tbl4_x 4400.0) (+ tbl4_y 350.0) 0.0) 170.0 "ИС_Текст_Основной" "C")
  (_r (list tbl4_x (- tbl4_y 5000.0) 0.0) (list (+ tbl4_x tbl4_w) tbl4_y 0.0) "ИС_Таблицы_Сетка")
  (_l (list tbl4_x (- tbl4_y 700.0) 0.0) (list (+ tbl4_x tbl4_w) (- tbl4_y 700.0) 0.0) "ИС_Таблицы_Сетка")
  (_t "№" (list (+ tbl4_x 300.0) (- tbl4_y 450.0) 0.0) 120.0 "ИС_Текст_Основной" "C")
  (_t "Наименование конструкций / работ" (list (+ tbl4_x 2600.0) (- tbl4_y 450.0) 0.0) 120.0 "ИС_Текст_Основной" "C")
  (_t "Класс бетона" (list (+ tbl4_x 5400.0) (- tbl4_y 450.0) 0.0) 120.0 "ИС_Текст_Основной" "C")
  (_t "Ед." (list (+ tbl4_x 6400.0) (- tbl4_y 450.0) 0.0) 120.0 "ИС_Текст_Основной" "C")
  (_t "Объем" (list (+ tbl4_x 7100.0) (- tbl4_y 450.0) 0.0) 120.0 "ИС_Текст_Основной" "C")
  (_t "Примечание" (list (+ tbl4_x 8000.0) (- tbl4_y 450.0) 0.0) 120.0 "ИС_Текст_Основной" "C")
  (foreach vx (list 600.0 4600.0 6100.0 6700.0 7500.0)
    (_l (list (+ tbl4_x vx) (- tbl4_y 5000.0) 0.0) (list (+ tbl4_x vx) tbl4_y 0.0) "ИС_Таблицы_Сетка")
  )
  (setq rows4 '(
    ("1" "Монолитный ленточный ростверк" "В20 W4 F100" "м3" "3.66" "Сечение перем.")
    ("2" "Буронабивные сваи d=200 мм" "В20 W4 F100" "м3" "0.14" "7 свай по 0.65 м")
    ("ИТОГО" "Бетон тяжелый ГОСТ 26633-2015" "В20 (М250)" "м3" "3.80" "Паспорт качества")
    ("4" "Устройство щитовой опалубки ростверка" "—" "м2" "16.20" "Доска 40 мм")
    ("5" "Обмазочная гидроизоляция фундаментов" "Битум" "м2" "18.50" "Горячий битум х2")
    ("6" "Уход за бетоном (укрытие, полив)" "—" "м2" "18.50" "7 суток (СП 70)")
  ))
  (setq cur_ry (- tbl4_y 700.0))
  (foreach r rows4
    (setq cur_ry (- cur_ry 700.0))
    (_l (list tbl4_x cur_ry 0.0) (list (+ tbl4_x tbl4_w) cur_ry 0.0) "ИС_Таблицы_Тонкая")
    (_t (nth 0 r) (list (+ tbl4_x 300.0) (+ cur_ry 230.0) 0.0) 120.0 "ИС_Текст_Основной" "C")
    (_t (nth 1 r) (list (+ tbl4_x 700.0) (+ cur_ry 230.0) 0.0) 120.0 "ИС_Текст_Основной" "L")
    (_t (nth 2 r) (list (+ tbl4_x 5350.0) (+ cur_ry 230.0) 0.0) 120.0 "ИС_Текст_Основной" "C")
    (_t (nth 3 r) (list (+ tbl4_x 6400.0) (+ cur_ry 230.0) 0.0) 120.0 "ИС_Текст_Основной" "C")
    (_t (nth 4 r) (list (+ tbl4_x 7100.0) (+ cur_ry 230.0) 0.0) 120.0 "ИС_Текст_Основной" "C")
    (_t (nth 5 r) (list (+ tbl4_x 7600.0) (+ cur_ry 230.0) 0.0) 110.0 "ИС_Текст_Основной" "L")
  )

  (setq nt_y (- cur_ry 400.0))
  (_t "ТЕХНИЧЕСКИЕ ТРЕБОВАНИЯ И ПРИМЕЧАНИЯ:" (list tbl4_x nt_y 0.0) 135.0 "ИС_Текст_Основной" "L")
  (_t "1. Бетонирование производить тяжелым бетоном класса В20 W4 F100 по ГОСТ 26633-2015." (list tbl4_x (- nt_y 250.0) 0.0) 115.0 "ИС_Текст_Основной" "L")
  (_t "2. Уплотнение бетонной смеси производить глубинным вибратором (наконечник d<=38мм)." (list tbl4_x (- nt_y 480.0) 0.0) 115.0 "ИС_Текст_Основной" "L")
  (_t "3. Обеспечить влажностный уход за уложенным бетоном в течение не менее 7 суток." (list tbl4_x (- nt_y 710.0) 0.0) 115.0 "ИС_Текст_Основной" "L")
  (_t "4. Распалубку производить при достижении бетоном не менее 70% проектной прочности." (list tbl4_x (- nt_y 940.0) 0.0) 115.0 "ИС_Текст_Основной" "L")
  (_t "5. Поверхности ростверка, соприкасающиеся с грунтом, обмазать горячим битумом за 2 раза." (list tbl4_x (- nt_y 1170.0) 0.0) 115.0 "ИС_Текст_Основной" "L")

  ;; ЗУМИРОВАНИЕ НА НОВЫЕ ИСПРАВЛЕННЫЕ СХЕМЫ
  (command "_.zoom" "_w" (list (- b1_x 1000.0) (- by_v2 1000.0) 0.0) (list (+ b4_x 22000.0) (+ by_v2 16000.0) 0.0))
  (setvar "CMDECHO" old_echo)
  (setvar "OSMODE" old_osm)
  (princ "\n=======================================================\n")
  (princ "\n ИСПРАВЛЕННЫЕ СХЕМЫ УСПЕШНО ПОСТРОЕНЫ (НИЖНИЙ РЯД)! \n")
  (princ "\n=======================================================\n")
  (princ)
)

(c:CREATE_POPOVKA_SCHEMES_V2)
